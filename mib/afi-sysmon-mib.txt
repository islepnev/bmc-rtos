AFI-SYSMON-MIB DEFINITIONS ::= BEGIN

IMPORTS
    OBJECT-TYPE
        FROM RFC-1212
    enterprises
        FROM RFC1155-SMI
    DisplayString
        FROM RFC1213-MIB;

jinr MODULE-IDENTITY
    LAST-UPDATED "201904100000Z"
    ORGANIZATION "JINR"
    CONTACT-INFO
         "email:    islepnev@jinr.ru"
    DESCRIPTION
        " JINR SNMP Management Information Base "
    ::= { enterprises 26381 }

afi MODULE-IDENTITY
    LAST-UPDATED "201904100000Z"
    ORGANIZATION "AFI Electronics"
    CONTACT-INFO
         "email:    islepnev@jinr.ru"
    DESCRIPTION
        " AFI Electronics SNMP Management Information Base "
    ::= { jinr 120 }

sysmon              OBJECT IDENTIFIER ::= { afi 1 }
sensors             OBJECT IDENTIFIER ::= { sysmon 1 }

sensorsTable OBJECT-TYPE
    SYNTAX  SEQUENCE OF VoltageEntry
    ACCESS  not-accessible
    STATUS  mandatory
    DESCRIPTION
           "A list of power supply sensors."
    ::= { sensors 1 }

sensorsEntry OBJECT-TYPE
    SYNTAX  VoltageEntry
    MAX-ACCESS  not-accessible
    STATUS  mandatory
    DESCRIPTION
            "A table row"
    INDEX   { sensorsIndex }
    ::= { sensorsTable 1 }

VoltageEntry ::=
    SEQUENCE {
        sensorsIndex
            INTEGER,
        sensorsName
            DisplayString,
        sensorsStatus
            INTEGER,
        sensorsVoltage
            INTEGER,
        sensorsCurrent
            INTEGER,
    }
sensorsIndex OBJECT-TYPE
    SYNTAX  INTEGER
    ACCESS  read-only
    STATUS  mandatory
    DESCRIPTION
            "An index for the sensors"
    ::= { sensorsEntry 1 }

sensorsName OBJECT-TYPE
    SYNTAX  DisplayString
    ACCESS  read-only
    STATUS  mandatory
    DESCRIPTION
            "The name of the sensor"
    ::= { sensorsEntry 2 }

sensorsState OBJECT-TYPE
    SYNTAX  INTEGER   { Unknown (0), Normal (1), Warning (2), Critical (3) }
    ACCESS  read-only
    STATUS  mandatory
    DESCRIPTION
            "The current state of the sensor"
    ::= { sensorsEntry 3 }

sensorsVoltage OBJECT-TYPE
    SYNTAX  INTEGER
    ACCESS  read-only
    STATUS  mandatory
    DESCRIPTION
            "The voltage reading of the sensor in mV"
    ::= { sensorsEntry 4 }

sensorsCurrent OBJECT-TYPE
    SYNTAX  INTEGER
    ACCESS  read-only
    STATUS  mandatory
    DESCRIPTION
            "The current reading of the sensor in mA"
    ::= { sensorsEntry 5 }


sensorsCount OBJECT-TYPE
    SYNTAX  INTEGER
    ACCESS  read-only
    STATUS  mandatory
    DESCRIPTION
            "Number of sensors"
    ::= { afi 2 }

END
